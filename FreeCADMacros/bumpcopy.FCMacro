from FreeCAD import Base
number=7
ang=360/number
sel = FreeCADGui.Selection.getSelection()
sel = sel[0]
name = sel.Name
shape = sel.Shape
for i in range(1,number):
     newshape = sel.Shape.copy()   
     #newshape.rotate(Base.Vector(21.5,40,0),Base.Vector(0,0,1),i*ang) 
     newshape.rotate(Base.Vector(0,0,0),Base.Vector(0,0,1),i*ang)    
     newobject = FreeCAD.ActiveDocument.addObject("Part::Feature",name)
     newobject.Shape = newshape
