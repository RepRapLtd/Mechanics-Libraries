# FreeCAD Python Macro to make M series nuts
#
# Adrian Bowyer
# reprapltd.com
#
# 22 April 2019
#
# Licence: GPL
#

import random
import Part, FreeCAD, math
from FreeCAD import Base

# Parameters

#M2
#NutHoleWidth = 4
#depth = 1.6
#NutName= "M2 Nut Hole"

#M2.5
NutHoleWidth = 5
depth = 2
NutName= "M2.5 Nut Hole"

#M3
#NutHoleWidth = 5.6
#depth = 6
#NutName= "M3 Nut Hole"

#M3 nylock
#NutHoleWidth = 5.5
#depth=4
#NutName= "M3 Nylock Nut Hole"

#M4
#NutHoleWidth = 7
#depth = 3
#NutName= "M4 Nut Hole"

#M5
#NutHoleWidth = 8.4
#depth = 10 #3.7 actual
#NutName= "M5 Nut"

#M6
#NutHoleWidth = 10
#depth = 4.8
#NutName= "M6 Nut Hole"

#M8 fine
#NutHoleWidth = 13
#depth = 6.2
#NutName= "M8 Nut Hole"

#M10
#NutHoleWidth = 17
#depth = 10
#NutName= "M10 Nut Hole"


#********************************************************************************

def hexagon(r, l):
 c = Part.makeCylinder(2*r, l, Base.Vector(0,0,0), Base.Vector(0,0,1), 360)
 b = Part.makeBox(2*r, 2*r, 1.2*l)
 b.translate(Base.Vector(-r, r, -0.1*l))
 a = b
 ang=360/6
 for i in range(1,6):
  newshape = b.copy()   
  newshape.rotate(Base.Vector(0,0,0),Base.Vector(0,0,1),i*ang)    
  a = a.fuse(newshape)
 a = c.cut(a)
 return a

b = hexagon(NutHoleWidth/2, depth)
obj=App.ActiveDocument.addObject('Part::Feature',NutName)
obj.Shape=b
#Part.show(b)
