# Beech Design Scanner Simulation
# Adrian Bowyer
# 19 February 2020

import Part, Draft, BOPTools, FreeCAD, math, copy, sys
from FreeCAD import Base
import PySide
from PySide import QtGui, QtCore
from PIL import Image, ImageDraw, ImageFilter
from random import seed
from random import gauss
import PySide

#-----------------------------------------------------------------------------------------------------------------------------------------------------------------------------

tooShort = 10
scale = 0.06

def PlotTriangle(t):
 l0 = Part.makeLine(t[0], t[1])
 l1 = Part.makeLine(t[1], t[2])
 l2 = Part.makeLine(t[2], t[0])
 wire = Part.Wire([l0, l1, l2])
 face = Part.Face(wire)
 Part.show(face)

def GaussTripple(size):
 m0 = gauss(0.0, size*scale)
 m1 = gauss(0.0, size*scale)
 m2 = gauss(0.0, size*scale)
 return ((m0, m1, m2)) 

def SplitTriangle(t, m):
 v0 = t[0]
 v1 = t[1]
 v2 = t[2]
 size = 0.0
 l = v1.sub(v0).Length
 size += l
 if l < tooShort:
  PlotTriangle(t)
  return
 l = v2.sub(v1).Length
 size += l
 if l < tooShort:
  PlotTriangle(t)
  return
 l = v0.sub(v2).Length
 size += l
 if l < tooShort:
  PlotTriangle(t)
  return
 size = size/3.0
 #print(size)
 mid0 = v0.add(v1)
 mid0.multiply(0.5)
 mid1 = v1.add(v2)
 mid1.multiply(0.5)
 mid2 = v2.add(v0)
 mid2.multiply(0.5)
 mid0 = Base.Vector(mid0.x, mid0.y, mid0.z + m[0])
 mid1 = Base.Vector(mid1.x, mid1.y, mid1.z + m[1])
 mid2 = Base.Vector(mid2.x, mid2.y, mid2.z + m[2])
 gt0 = GaussTripple(size)
 gt1 = GaussTripple(size)
 gt2 = GaussTripple(size)

 SplitTriangle((v0, mid0, mid2), gt0)
 SplitTriangle((v1, mid1, mid0), gt1)
 SplitTriangle((v2, mid2, mid1), gt2)
 SplitTriangle((mid0, mid1, mid2), (gt1[1], gt2[1], gt0[1]))

v0 = Base.Vector(0.0, 0.0, 0.0)
v1 = Base.Vector(0.0, 100.0, 0.0)
v2 = Base.Vector(100.0, 0.0, 0.0)

SplitTriangle((v0, v1, v2), GaussTripple(100))
