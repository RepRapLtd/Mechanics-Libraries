from FreeCAD import Base
import copy 
number=6
distance=5
direction = Base.Vector(distance,0,0)
sel = FreeCADGui.Selection.getSelection()
sel = sel[0]
name = sel.Name
shape = sel.Shape
for i in range(1,number):
     newshape = sel.Shape.copy()   
     #newshape.rotate(Base.Vector(21.5,40,0),Base.Vector(0,0,1),i*ang)
     d = copy.deepcopy(direction)
     d = d.multiply(i) 
     newshape.translate(d)    
     newobject = FreeCAD.ActiveDocument.addObject("Part::Feature",name)
     newobject.Shape = newshape
