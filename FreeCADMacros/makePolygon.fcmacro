pts=[
 App.Vector(0, 0, 0),
 App.Vector(5.5, 6.4, 0),
 App.Vector(15.5, 12.5, 0),
 App.Vector(25.5, 16.2, 0),
 App.Vector(35.5, 18.75, 0),
 App.Vector(45.5, 20.33, 0),
 App.Vector(55.5, 21.3, 0),
 App.Vector(65.5, 22.1, 0),
 App.Vector(75.5, 22.73, 0),
 App.Vector(85.5, 23, 0),
 App.Vector(95.5, 23.53, 0),
 App.Vector(105.5, 23.53, 0),
 App.Vector(115.5, 23.53, 0),
 App.Vector(125.5, 23.68, 0),
 App.Vector(135.5, 23.49, 0),
 App.Vector(145.5, 23.1, 0),
 App.Vector(155.5, 23.08, 0),
 App.Vector(165.5, 22.42, 0),
 App.Vector(175.5, 21.81, 0),
 App.Vector(185.5, 20.91, 0),
 App.Vector(195.5, 20.37, 0),
 App.Vector(205.5, 19.37, 0),
 App.Vector(215.5, 18.13, 0),
 App.Vector(225.5, 16.28, 0),
 App.Vector(235.5, 14.64, 0),
 App.Vector(245.5, 12.38, 0),
 App.Vector(255.5, 10.2, 0),
 App.Vector(265.5, 7.38, 0),
 App.Vector(275.5+4.4-0.95, 1, 0),
 App.Vector(275.5+4.4, 0, 0)
 ]
pts
import Part
wire=Part.makePolygon(pts)
face=Part.Face(wire)
Part.show(face)
